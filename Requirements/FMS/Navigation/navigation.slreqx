# navigation

## NAV-FUNC: The system provides functions to edit the flight plan (Functional)
module NAV:
manage the flight plan,
link waypoints to create legs

### NAV-X: The system shall compute a flight plan from pilot input (Functional)
-decode pilot input
-select a flight plan
-edit a flight plan
-perform copies

### NAV-FP: The system shall describea flight plan (Functional)
-list of ordered waypoints
-contains departure, arrival and possibly alternate APT
-contains wind information
-indications : Flight Number, CI, Masses, etc.. as described in documentation
-compute predictions

### NAV-FP-TEMP: The temporary FP shall help pilot to visualize modifications to selected FP (Functional)
-get prim (=active) FP
-modify it
-return a temporary FP
computes time and fuel predictions

### NAV-FP-PRIM: The system shall modify and follow the primary flight plan (Functional)
input : init data or full flight plan
output : flight plan and predictions
contains flight plan data
computes time and fuel predictions

### NAV-FP-SEC: The system shall contain a secondary flight plan (Functional)
input: init data or flight plan
output: flight plan
computes time and fuel predictions
