# FlightManagementSystem

## FUNC_FMS (Functional)

### NAV-FUNC: The system compute a trajectory following the flight plan (Functional)
module NAV:
manage the flight plan,
compute legs and transitions

### GUID-FUNC: The system determine the desired route from flight plan (Functional)
Module Guidage
compute the active leg
compute the track errors (cross track, angle error)

### CONTROL-FUNC: The system shall determine the attitude from desired route (Functional)
Module Control:
compute the desired attitude from the route computed by guidance
