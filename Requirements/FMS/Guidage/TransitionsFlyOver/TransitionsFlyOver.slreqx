# TransitionsFlyOver

## GUID-FUNC-6: The system shall determine the fly-over transitions. (Functional)
- Rationale: The fly-over transitions are used when asked.

### GUID-FUNC-6.1: The system shall compute transition parameters for the fly-over transitions (Functional)

#### GUID-FUNC-6.1.1: The system shall compute the track change (alpha) between two legs in degrees. (Functional)
This function’s inputs are two given legs. The track change is the angle between the two legs considered.
- Rationale: The track change between two legs is used as an input for the calculation of a transition.

#### GUID-FUNC-6.1.2: The system shall compute the lead distance, the turn radius and the bank angle of the considered transition. (Functional)
This function’s inputs are the transition to compute, the true air speed (TAS), the track change (alpha) and the list of legs.
- Rationale: A transition is defined by a lead distance, a turn radius and a bank angle. A transition is defined by a lead distance, a turn radius and a bank angle.

#### GUID-FUNC-6.1.3: The system shall compute the lead distance, the turn radius and the bank angle of the considered transition, considering the algorithm described. (Functional)
This function’s inputs are the transition to compute, the true air speed (TAS), the track change (alpha) and the list of legs. All the numeric values are taken from DO-236C §3.2.5.4 and Airbus specifications.
g = 9.807 m.s^{-2}
- Rationale: A transition is defined by a lead distance, a turn radius and a bank angle.

#### GUID-FUNC-6.1.4: The system shall provide the true air speed for the calculation of the transition to compute. The selected true air speed is the predicted true air speed (from the prediction module). (Functional)
This function’s inputs are the list of legs, the active leg, the transition to compute and the speed predictions.
- Rationale: True air speed is an input for the calculation of the transitions.

#### GUID-FUNC-6.1.5: The system shall provide the altitude for the calculation of the transition to compute. The selected altitude is the predicted altitude (from the prediction module). (Functional)
- Rationale: Altitude is an input for the calculation of the transitions.

### GUID-FUNC-6.2: The system shall build the reference lateral path of the plane. (Functional)
The reference lateral path corresponds to the actual path meant to be flown by the aircraft.
- Rationale: The reference lateral path is an information sent to the autopilot, and send to be displayed by the EFIS.

#### GUID-FUNC-6.2.1: The system shall convert the course into a track. (Functional)
Track and Course are the terms used for a course but respectively in radians (with Track in [ -pi; pi]) and in degrees (with Course in [0; 360°]).
The course is in degrees and belongs to the interval [0; 360°] Track is positive to the right. Track must be converted in radians and belongs to [-pi; pi]
- Rationale: The track of a leg is used to compute the track change between two legs.

#### GUID-FUNC-6.2.2: The system shall build the reference first turn centre. (Functional)
The distance between the transition point and the turn centre is [B, Bc] = lead distance.
The first turn centre is determined in function of the first track and track change (which allows us to determine the bank angle as we could do in a fly-over transition)
Assumption :
The reference lateral path corresponds to the actual path meant to be flown by the aircraft.
- Rationale: The reference lateral path is an information sent to the autopilot, and send to be displayed by the EFIS.

#### GUID-FUNC-6.2.4: The system shall determine the pseudo-waypoint disposed in the next leg as the projection of the 30° higher track leg. (Functional)
- Rationale: The second turn centre is an important information to compute the second transition.

#### GUID-FUNC-6.2.3: The system shall build the end of the turn. (Functional)
The beginning of the turn will be calculated with the different parameters (such as the lead distance, the track of the leg, the turn radius, the bank angle, etc.).
- Rationale: The end of the first transition is an information sent to the SEQ group to compute the real trajectory of the plane.

#### GUID-FUNC-6.2.5: The system shall build the reference second turn centre. (Functional)
This transition is computed like a fly-by transition between the 30° higher track leg and the next leg.
- Rationale: The second turn centre is an information sent to the SEQ group to compute the real trajectory of the plane.

#### GUID-FUNC-6.2.6: The system shall build the beginning of the second turn. (Functional)
This transition is computed like a fly-by transition between the 30° higher track leg and the next leg. The beginning of the turn will be calculated with the different parameters (such as the lead distance, the track of the leg, the turn radius, the bank angle, etc.).
- Rationale: The beginning of the second transition is an information sent to the SEQ group to compute the real trajectory of the plane.

#### GUID-FUNC-6.2.7: The system shall build the end of the second turn. (Functional)
The beginning of the turn will be calculated with the different parameters (such as the lead distance, the track of the leg, the turn radius, the bank angle, etc.).
- Rationale: The end of the second transition is an information sent to the SEQ group to compute the real trajectory of the plane.

#### GUID-FUNC-6.2.8: The system shall compute the different data from a transition, and create a list of mixed great circle leg and transition between the beginning and the end of the turn. (Functional)
This transition is computed like a fly-by transition between the 30° higher track leg and the next leg.
The reference flight path is defined by a list of:
- Great circle distance between the point of exit of the past transition and the point of entry of the next transition;
- Transition defined by circular arcs starting at the point of entry of the transitions and ending at the point of exit of the first transition, the virtual turn centre;
- Great circle distance between the point of exit of the first transition and the point of entry of the second transition;
- Transition defined by circular arcs starting at the point of entry of the transitions and ending at the point of exit of the second transition, the virtual turn centre;
- Rationale: The end of the second transition is an information sent to the SEQ group to compute the real trajectory of the plane.

### GUID-FUNC-6.3: The system shall compute the automatic sequencing conditions. (Functional)

#### GUID-FUNC-6.3.1: The system shall compute the automatic sequencing conditions. When the Transition is a Fly-over, the se- quencing condition is the active waypoint. When the projected position of the aircraft coincides with the waypoint’s position, the aircraft cross (Functional)
This function inputs are the state vector, and the current trajectory's path.
Assumption :
Sequencing conditions take into account if the system is on HDG or NAV mode.
- Rationale: The sequencing conditions give a point in order to know when the aircraft crosses from the
  Ortho to the Transition.
