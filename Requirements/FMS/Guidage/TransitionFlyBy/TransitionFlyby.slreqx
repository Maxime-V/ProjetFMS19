# TransitionFlyby

## GUID-FUNC-5: The system shall determine the fly-by transitions (Functional)
The fly-by transitions are used to turn in nominal cases

### GUID-FUNC-5.1: The systeme shall compute transition parameters of the fly-by transition (Functional)

#### GUID-FUNC-5.1.1: The system shall compute the track change (alpha) between two legs in degrees. (Functional)
Comments :
This function’s inputs are two given legs. The track change is the angle between the two legs considered.
- Rationale: The track change between two legs is used as an input for the calculation of a transition.

#### GUID-FUNC-5.1.2: The system shall compute the lead distance, the turn radius and the bank angle of the considered transition, considering the algorithm described. (Functional)
Assumption:
g = 9.807 m.s^{-2}
Comments:
This function’s inputs are the transition to compute, the true air speed (TAS), the track change (alpha) and the list of legs. All the numeric values are taken from DO-236C §3.2.5.4 and Airbus specifications.
- Rationale: A transition is defined by a lead distance, a turn radius and a bank angle.

#### GUID-FUNC-5.1.3: The system shall provide the true air speed for the calculation of the transition to compute. The selected true air speed is the predicted true air speed (from the prediction module). (Functional)
Comments:
This function’s inputs are the list of legs, the active leg, the transition to compute and the speed predictions.
- Rationale: True air speed is an input for the calculation of the transitions.

#### GUID-FUNC-5.1.4: The system shall provide the altitude for the calculation of the transition to compute. The selected altitude is the predicted altitude (from the prediction module). (Functional)
- Rationale: Altitude is an input for the calculation of the transitions.

### GUID-FUNC-5.2: The system shall build the reference lateral path of the plane. (Functional)
Assumption:
The reference lateral path corresponds to the actual path meant to be flown by the aircraft.
- Rationale: The reference lateral path is an information sent to the autopilot, and send to be displayed by the EFIS.

#### GUID-FUNC-5.2.1: The system shall convert the course into a track. (Functional)
Assumption:
-The course is in degrees and belongs to the interval [0; 360°]
-Track is positive to the right.
-Track must be converted in radians and belongs to [-pi; pi]
Comments:
Track and Course are the terms used for a course but respectively in radians (with Track in [ -pi; pi]) and in degrees (with Course in [0; 360°]).
- Rationale: The track of a leg is used to compute the track change between two legs.

#### GUID-FUNC-5.2.2: The system shall build the reference turn centre. (Functional)
Assumption :
The distance between the transition point and the turn centre is [B, Bc] = sqrt{turn radius² + lead distance^2}. Angle(A,B,Bc) = \frac{180 – alpha)}{2}"
- Rationale: The turn centre is an information sent to the SEQ group to compute the real trajectory of the plane.

#### GUID-FUNC-5.2.3: The system shall build the beginning of the turn. (Functional)
Comments:
The beginning of the turn will be calculated with the different parameters (such as the lead distance, the track of the leg, the turn radius, the bank angle, etc.).
- Rationale: The beginning of the transition is an information sent to the SEQ group to compute the real trajectory of the plane.

#### GUID-FUNC-5.2.4: The system shall build the end of the turn. (Functional)
Assumption :
The end of the turn will be calculated with the different parameters (such as the lead distance, the track of the leg, the turn radius, the bank angle, etc.).
- Rationale: The end of the transition is an information sent to the SEQ group to compute the real trajectory of the plane.

#### GUID-FUNC-5.2.5: The system shall compute the different data from a transition, and create a list of mixed great circle leg and transition between the beginning and the end of the turn. (Functional)
Comments :
The reference flight path is defined by a list of:
- Great circle distance between the point of exit of the past transition and the point of entry of the next transition;
- Transition defined by circular arcs starting at the point of entry of the transitions and ending at the point of exit of the transitions, the virtual turn centre.
- Rationale: The end of the transition is an information sent to the SEQ group to compute the real trajectory of the plane.

### GUID-FUNC-5.3: The system shall compute the automatic sequencing conditions. (Functional)

#### GUID-FUNC-5.3.1: The system shall compute the automatic sequencing conditions. (Functional)
The system shall compute the automatic sequencing conditions. When the Transition is a Fly-by, the sequencing condition is the line equation between the virtual turn center of the Transition and the active waypoint, referenced as the bisector of the Transition. It is hence a function of the aircraft coordinates and will be noted by f(x,y).
Assumption :
Sequencing conditions take into account if the system is on HDG or NAV mode.
Comments :
This function’s inputs are the reference lateral , the active Leg and the aircraft position. The turn center and active waypoint are known from the reference lateral .
- Rationale: The sequencing condition gives the line equation in order to know when the aircraft reaches the middle of the Transition.
