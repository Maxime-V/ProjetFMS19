# guidance

## GUID-FUNC (Functional)

### GUID-FUNC-1: The system shall know the active leg at all times (Functional)

### GUID-FUNC-2: The system shall compute transitions and follow the progress of the active leg (Functional)

### GUID-FUNC-3: The system shall compiute the distance between the aircraft's current position and the active waypoint. (Functional)

### GUID-FUNC-4: The system shall manage complex transitions and discontinuity cases (Functional)
Assumption:
The function is not provided at the moment, TODO in further versions
- Rationale: The system has to provide a flyable reference path, even if a leg is too short to connect the fly-by transition.

### GUID-FUNC-5: The system shall determine the fly-by transitions (Functional)
The fly-by transitions are used to turn in nominal cases

### GUID-FUNC-6: The system shall determine the fly-over transitions (Functional)
- Rationale: The fly-over transitions are used when asked

### GUID-FUNC-7: Compute the different data from all the transitions, and create a list of paths (including fly-by or fly-over transitions). (Functional)
Transitions are calculated with the different parameters (the active leg, the track change alpha, the lead distance, bank angle and turn radius of the next two transitions. Be careful to recalculate the track change, the lead distance, the bank angle and the turn radius for each transition).
Assumption :
The entire list of legs is given at preflight.
- Rationale: The reference lateral path is an information sent to the autopilot, and sent to be displayed by the EFIS

### GUID-FUNC-8: The system shall, every 5 seconds, when the aircraft exits a transition or when the flight plan is modified, get the next transition and the next second transition. (Functional)
- Rationale: To be able to compute the next two transitions.

### GUID-FUNC-9: The system shall, every 5 seconds, when the aircraft exits a transition or when the flight plan is modified, get the speed prediction information.} {To use this speed in the computation of the next two transitions. (Functional)
Assumption :
The assumed true air speed is constant during a transition.
- Rationale: To use this speed in the computation of the next two transitions.

### GUID-FUNC-10: The system shall be able to compute the different data from the 2 next transitions, and create a list of paths (including fly-by or fly-over transitions). (Functional)
Transitions are calculated with the different parameters (the active leg, the track change alpha, the lead distance, bank angle and turn radius of the next two transitions. Be careful to recalculate the track change, the lead distance, the bank angle and the turn radius for each transition).
Assumption :
The list of next paths (great circle distance + transition) is given every 5 seconds to update the trajectory.
It only corresponds to the trajectory to go through the next two transitions. The rest of the lateral path is the track to fix legs of the list of legs.
- Rationale: This temporary reference lateral path is an information sent to the autopilot, and send to be displayed by the EFIS.
  This function shall be computed every 5 second for the SEQ group.

### GUID-FUNC-11: The system shall, once a new transition has been computed, update the reference lateral path. (Functional)
- Rationale: To display the reference lateral path on the Navigation Display.

### GUID-FUNC-12: The system shall, every 5 seconds of when the aircraft exists a transition or when the flight plan is modified, send to HMI the reference lateral path. (Functional)
Assumption :
The reference lateral path is displayed once it has been updated.
- Rationale: To show to the pilot the exact trajectory he has to follow.

### GUID-FUNC-13: The prediction submodule shall compute the set of speed predictions. This system requests the list of legs sent by LEGS module and the maximum speed allowed given for each leg. (Functional)
The speed predictions should be available to the other functions in a dictionary where each speed prediction is linked with a leg ID. The predictions refer to the predicted ground speeds at the leg termination.
Assumption :
It doesn't take into account weather conditions or parameters which are hard to calculate without a particular database. It only takes into account the cost index, the wind and CRZ_ALT given by the pilot.
- Rationale: The speed predictions are to be used to compute the transition parameters and to give the altitude which have to be followed by the aircraft.

### GUID-FUNC-14: The prediction submodule shall compute the set of altitude predictions. This system requests the list of legs and the maximum and minimum altitudes (FL) allowed given for each leg. (Functional)
The altitude predictions should be available to the other functions in a dictionary where each altitude prediction is linked with a leg ID. The predictions refer to the predicted altitude at the leg termination.
Assumption :
The prediction submodule doesn't take into weather conditions or parameters difficult to calculate without a particular Database. It only takes into account cost index, wind and CRZ_ALT given by the pilot.
- Rationale: The altitude predictions are to be used to compute the transition parameters and to give the speed which have to be followed by the aircraft.

### GUID-FUNC-15: The prediction submodule shall send the predictions to transition. (Functional)
Assumption :
Information could also be sent to HMI using QtSignals.
- Rationale: The predictions are to be used to compute the transition parameters and to give the speed and altitude which have to be followed by the A/C.
