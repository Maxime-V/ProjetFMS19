# activeleg

## GUID-FUNC-1: The system shall know the active leg (Functional)

### GUID-FUNC-1.1: Before departure, the active leg is the first leg (Functional)
#######################
This function’s inputs are the list of Legs. This requirement only addresses the pre-flight
initialization.
- Rationale: Active Leg is an input used to build the reference lateral and to compute the commands.

### GUID-FUNC-1.2: When condition are met, the next leg shall become the active leg (Functional)
The system shall be able to sequence the active Leg. In Fly-over, the (x,y) coordinates are taken from the aircraft
state. If the sequencing condition that will be written as f(x,y)≥0 is true, it means the aircraft has intersected
with the bisector (line between the active waypoint and the center of the Transition circle). Then the active Leg
shall be set to the next Leg. If f(x,y)<0, the aircraft has still not reached the bisector. In this case, the system
shall keep the current active Leg as the active Leg. In , we sequence when the aircraft pass from an Ortho to a
Transition. In fact, when the aircraft cross the end point of the Ortho.
Assumption:
To compute sequencing conditions XTK shall be inferior to 5NM, only in HDG mode
Comments:
This function’s inputs are the bisector of the Transition, the active waypoint and the aircraft
position.
- Rationale: The sequencing of the aircraft allows the system to evaluate the moment the active Leg is
  updated when the aircraft is flying the Transition. It is triggered by the automatic sequencing
  condition.
