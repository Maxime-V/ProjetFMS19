# segmentTransition

## GUID-FUNC-2: The system shall compute transitions and follow the progress of the active leg (Functional)

### GUID-FUNC-2.1: The system shall compute fly-by or fly-over transitions according to the waypoints (Functional)
Assumption: fixed-radius transitions are not supported in this version
- Rationale: For simplification. IOther types of transitions will be addressed in further versions of the document.

### GUID-FUNC-2.2: The system shall compute the projection of a point on a segment (Functional)
It is used by CalculDistance and Segment,

### GUID-FUNC-2.3: The system shall sequence from an Ortho to a Transition and also from Transition to an Ortho. (Functional)
Assumption: There are two different Transitions (Fly-by, Fly-over). The type of Transition is an input used
to compute others functions
- Rationale: A leg is constituted of one segment and one Transition. The sequencing conditions:
  • If the projection is between the start point and the end point of the Ortho defined during the trajectory,
  the aircraft is on Ortho.
  • Otherwise the aircraft is on the Transition
