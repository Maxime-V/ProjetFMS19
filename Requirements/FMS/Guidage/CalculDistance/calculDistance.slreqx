# calculDistance

## GUID-FUNC-3: The system shall compiute the distance between the aircraft's current position and the active waypoint (Functional)

### GUID-FUNC-3.1: The system shall compute the Direct distance between the aircraft's current position and the active waypoint. (Functional)

### GUID-FUNC-3.2: The system shall compute the Along path distance to the active waypoint. (Functional)
Assumption: The Direct distance to the waypoint to the active waypoint is calculated in the aircraft level.
The difference of altitude between the aircraft and the active Leg is not considered.
Comment: This function’s inputs are the active waypoint coordinates and the aircraft position. The active
waypoint coordinates are stored in the active Leg.
- Rationale: The active waypoint coordinates are determined with the information of the active Leg. The coordinates of the projection of the active waypoint on the reference lateral (Ortho or Transition) is computed as the intersection of the reference lateral with the line equation between the virtual turn center of the Transition and the active waypoint. The system computes the length of the segment between the projection of the aircraft position on the trajectory and the projection of the active waypoint.The Direct distance to the waypoint is sent to the EFIS for operational purposes. The pilot can be requested to give it to the air traffic controller.
