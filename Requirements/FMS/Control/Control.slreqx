# Control

## CONT-FUNC-1: The system has 3 functional states. (Functional)
Summary :
The system has 3 functional states.
• ”Activated” state indicates the system is running.
• ”Deactivated” state indicates the system is off.
• ”Restart” state indicates the system is off because of errors but currently smooth restarting.
- Rationale: "Activated" and "Deactivated" are already existing for current used AP. We want to add "Restart"to clearly indicate that the system is out of order because of errors but is trying to correct them by rebooting.

## CONT-FUNC-2: The variables inside the software shall be protected from concurrent access of memory. (Functional)
We have chosen to use mutex.
- Rationale: Ivy is multi-threading architecture, so we need to share information between threads and protect them.

## CONT-FUNC-3: The system shall identify errors like faulty format inputs and lack of data. (Functional)
Alert, restart or deactivate application.
- Rationale: The system must be robust.

## CONT-FUNC-4: The system shall compute the bank angle objective within a maximum value of 30°. (Functional)
Saturations in our command law
- Rationale: https://www.skybrary.aero/index.php/Flight_Control_Laws}

## CONT-FUNC-5: The system shall compute the cross-track error (XTK). (Functional)
Summary :
The system shall compute the cross-track error (XTK). The XTK is the direct perpendicular distance between the aircraft position and the active leg. It is the smaller distance between the aircraft position and the points of the active leg. It is computed by expressing the equation of the perpendicular line to the trajectory that intersects the aircraft position. The XTK is signed according to the position of the aircraft with regards to the reference lateral path.
Assumption :
The difference of altitude between the aircraft position and the reference lateral path is not taken into account (that means that we consider the projection of the reference lateral path onto the altitude plan of the aircraft position). The altitude error is addressed by the Vertical Guidance module.
Comments :
This function’s inputs are the active \gls{leg}, reference lateral \gls{path} and the aircraft position.
- Rationale: The XTK is used to compute commands in order to keep the aircraft on its reference trajectory or to build a cross track correction trajectory. It will also be displayed on the EFIS.

## CONT-FUNC-6: The system shall compute the track angle error (TAE). (Functional)
The system shall compute the track angle error (TAE). The TAE is the angle between the aircraft track and the reference track. The reference track is the track of the projection point of the aircraft onto the active leg. The TAE is signed.
Assumption :
The reference lateral path is projected onto the aircraft level.
Comments :
The reference lateral path is projected onto the aircraft level. This function’s inputs are the active leg, the reference lateral path and the aircraft state.
- Rationale: The TAE is used to compute commands in order to keep the aircraft on its reference trajectory. It will also be displayed on the EFIS.

## CONT-FUNC-7: The system shall compute the track objective. (Functional)
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Comments :
The definition is different from that described in IENAC17 document because the COMM software do not access transitions information but access the commands. Moreover, because there is other modes, the track objective can be calculated only thanks to XTK and TAE.
- Rationale: The track objective is computed to be displayed on the EFIS.
