# req_nav

## NAV-FUNC-1.1.1 (Functional)
The FPLN-ROUTE module shall allow the pilot to initialize a flight plan by defining: FROM/TO airports and en-route elements such as airways, waypoints, or route sections (airway-waypoint couples)
- Rationale: To have the basic information for creating a flight plan
